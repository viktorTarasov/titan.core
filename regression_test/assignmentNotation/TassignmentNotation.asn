--/////////////////////////////////////////////////////////////////////////////
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kovacs, Ferenc
--   Raduly, Csaba
--
--/////////////////////////////////////////////////////////////////////////////
ASN-Definitions DEFINITIONS AUTOMATIC TAGS ::=
BEGIN
IMPORTS ; -- nothing

ASN-CSTR ::= CHARACTER STRING
ASN-SEQ-I ::= SEQUENCE (SIZE (1..10)) OF INTEGER
ASN-SEQ-R ::= SEQUENCE { asn-seq-i ASN-SEQ-I }

idx-ASN INTEGER ::= 0

END

--/////////////////////////////////////////////////////////////////////////////
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Baranyi, Botond
--
--/////////////////////////////////////////////////////////////////////////////

ImportingAsn DEFINITIONS AUTOMATIC TAGS ::=

BEGIN
-- EXPORTS <exports clause>;
IMPORTS

IICrequestTX, IICresponseTX FROM ImportedAsn { iso (1) standard (0) calm-management (24102) iitsscu (4) asnm-1 (1) }
;
-- MODULE-BODY

MYREALTYPE ::= REAL
-- MX-SAP generic OBJECT CLASS

MXSERV ::= CLASS {
      &mxref INTEGER(0..255),
      &MXParam
	}
	
MFSAP-CR::=MXSERV

iICrequestTX	MFSAP-CR::={&mxref 11, &MXParam IICrequestTX} 
iICresponseTX	MFSAP-CR::={&mxref 12, &MXParam IICresponseTX}

END

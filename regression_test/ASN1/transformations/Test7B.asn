--/////////////////////////////////////////////////////////////////////////////
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Koppany, Csaba
--   Kulcsar, Endre
--   Raduly, Csaba
--   Szabados, Kristof
--
--/////////////////////////////////////////////////////////////////////////////
Test7B --  B
DEFINITIONS

IMPLICIT TAGS


::=

BEGIN

IMPORTS ; -- nothing

MySequenceType1 ::= SEQUENCE
		{
		field1 [3] INTEGER OPTIONAL,
		field2 BOOLEAN OPTIONAL
		}

MySetType1 ::= SET
		{
		field1 [1] INTEGER OPTIONAL,
		field2 [0] BOOLEAN OPTIONAL
		}

MyChoiceType ::= CHOICE
		{
		field1 [5] INTEGER,
		field2 [6] BOOLEAN
		}


END

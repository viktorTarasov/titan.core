--/////////////////////////////////////////////////////////////////////////////
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Koppany, Csaba
--   Kulcsar, Endre
--   Raduly, Csaba
--   Szabados, Kristof
--
--/////////////////////////////////////////////////////////////////////////////
Test8B --  B
DEFINITIONS

IMPLICIT TAGS


::=

BEGIN

IMPORTS ; -- nothing

MySequenceType1 ::= SEQUENCE
		{
		field1 [0] INTEGER OPTIONAL,
		field2 [1] BOOLEAN OPTIONAL,
		field3 [2] EXPLICIT CHOICE {
				f1 [0] OCTET STRING,
				f2 [1] BIT STRING
			       		   }
		}

MySetType1 ::= SET
		{
		field1 [0] INTEGER OPTIONAL,
		field2 [1] BOOLEAN OPTIONAL,
		field3 [2] EXPLICIT CHOICE {
				f1 [0] OCTET STRING,
				f2 [1] BIT STRING
			       }
		}


MySequenceType2 ::= SEQUENCE
		{
		field1 [0] INTEGER OPTIONAL,
		field2 [1] BOOLEAN OPTIONAL,
		field3 [2] EXPLICIT MyChoiceType
		}

MySetType2 ::= SET
		{
		field1 [0]INTEGER OPTIONAL,
		field2 [1] BOOLEAN OPTIONAL,
		field3 [2] EXPLICIT MyChoiceType
		}



MyChoiceType ::= CHOICE
		{
		field1 [0] INTEGER,
		field2 [1] BOOLEAN
		}




END

--/////////////////////////////////////////////////////////////////////////////
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Raduly, Csaba
--
--/////////////////////////////////////////////////////////////////////////////
Test60

DEFINITIONS

AUTOMATIC TAGS

::=

BEGIN

IMPORTS ; -- nothing

MyIntegerType ::= INTEGER

myIntegerValue1 INTEGER ::= 1000

myIntegerValue2 MyIntegerType ::= -1000

myIntegerValue3 MyIntegerType ::= 0

myIntegerValue4 MyIntegerType ::= myIntegerValue1

myIntegerValue5 MyIntegerType ::= myIntegerValue2

myIntegerValue6 MyIntegerType ::= myIntegerValue3


END

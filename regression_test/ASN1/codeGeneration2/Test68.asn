--/////////////////////////////////////////////////////////////////////////////
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Koppany, Csaba
--   Kulcsar, Endre
--   Raduly, Csaba
--   Szabados, Kristof
--
--/////////////////////////////////////////////////////////////////////////////
Test68

DEFINITIONS

AUTOMATIC TAGS

::=

BEGIN

IMPORTS ; -- nothing

MyChoiceType1 ::= CHOICE
			    {
  			     field1 INTEGER,
			     field2 BOOLEAN,
			     field3 NULL,
			     field4 OCTET STRING,
			     field5 BIT STRING,
			     field6 ENUMERATED {a,b,c},
			     field7 REAL,
			     field8 MySequenceType1
			    }


MySequenceType1 ::= SEQUENCE {
  			     field1 INTEGER,
			     field2 BOOLEAN,
			     field3 NULL,
			     field4 OCTET STRING,
			     field5 BIT STRING,
			     field6 ENUMERATED {a,b,c},
			     field7 REAL
			    }


myChoiceValue1  MyChoiceType1 ::=   field1 : 1234

myChoiceValue2  MyChoiceType1 ::=   field2 : FALSE

myChoiceValue3  MyChoiceType1 ::=   field3 : NULL

myChoiceValue4  MyChoiceType1 ::=   field4 : '1234567890ABCDEF'H

myChoiceValue5  MyChoiceType1 ::=   field5 : '1010101010101010'B

myChoiceValue6  MyChoiceType1 ::=   field6 :  b

-- myChoiceValue7  MyChoiceType1 ::=   field7 : {mantissa 8,base 10, exponent -1}

myChoiceValue8  MyChoiceType1 ::=   field8 :
       {
        field1 555,                      -- INTEGER,
        field2 TRUE,                     -- BOOLEAN,
	field3 NULL,
	field4 'FF00'H,                  -- OCTET STRING,
	field5 '01010'B,                 -- BIT STRING,
	field6  a,                       --ENUMERATED {a,b,c},
	field7  5.3 --{mantissa 10,base 2, exponent 2}  --  --REAL
        }



END

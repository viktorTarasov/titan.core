--/////////////////////////////////////////////////////////////////////////////
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Feher, Csaba
--   Kovacs, Ferenc
--   Kulcsar, Endre
--   Raduly, Csaba
--
--/////////////////////////////////////////////////////////////////////////////
Test283
DEFINITIONS

AUTOMATIC TAGS

::=

BEGIN

IMPORTS ; -- nothing

action INTEGER ::= 1
activate INTEGER ::= 1
address INTEGER ::= 1
alive INTEGER ::= 1
all INTEGER ::= 1
alt INTEGER ::= 1
altstep INTEGER ::= 1
and INTEGER ::= 1
and4b INTEGER ::= 1
any INTEGER ::= 1
anytype INTEGER ::= 1
apply INTEGER ::= 1

bit2hex INTEGER ::= 1
bit2int INTEGER ::= 1
bit2oct INTEGER ::= 1
bit2str INTEGER ::= 1
bitstring INTEGER ::= 1
boolean INTEGER ::= 1
break INTEGER ::= 1

call INTEGER ::= 1
case INTEGER ::= 1
catch INTEGER ::= 1
char INTEGER ::= 1
char2int INTEGER ::= 1
char2oct INTEGER ::= 1
charstring INTEGER ::= 1
check INTEGER ::= 1
clear INTEGER ::= 1
complement INTEGER ::= 1
component INTEGER ::= 1
connect INTEGER ::= 1
const INTEGER ::= 1
continue INTEGER ::= 1
control INTEGER ::= 1
create INTEGER ::= 1

deactivate INTEGER ::= 1
decomp INTEGER ::= 1
default INTEGER ::= 1
derefers INTEGER ::= 1
disconnect INTEGER ::= 1
display INTEGER ::= 1
do INTEGER ::= 1
done INTEGER ::= 1

else INTEGER ::= 1
encode INTEGER ::= 1
enumerated INTEGER ::= 1
error INTEGER ::= 1
except INTEGER ::= 1
exception INTEGER ::= 1
execute INTEGER ::= 1
extends INTEGER ::= 1
extension INTEGER ::= 1
external INTEGER ::= 1

fail INTEGER ::= 1
false INTEGER ::= 1
float INTEGER ::= 1
float2int INTEGER ::= 1
float2str INTEGER ::= 1
for INTEGER ::= 1
from INTEGER ::= 1
function INTEGER ::= 1

getcall INTEGER ::= 1
getreply INTEGER ::= 1
getverdict INTEGER ::= 1
goto INTEGER ::= 1
group INTEGER ::= 1

halt INTEGER ::= 1
hex2bit INTEGER ::= 1
hex2int INTEGER ::= 1
hex2oct INTEGER ::= 1
hex2str INTEGER ::= 1
hexstring INTEGER ::= 1

if INTEGER ::= 1
ifpresent INTEGER ::= 1
import INTEGER ::= 1
in INTEGER ::= 1
inconc INTEGER ::= 1
infinity INTEGER ::= 1
inout INTEGER ::= 1
int2bit INTEGER ::= 1
int2char INTEGER ::= 1
int2float INTEGER ::= 1
int2hex INTEGER ::= 1
int2oct INTEGER ::= 1
int2str INTEGER ::= 1
int2unichar INTEGER ::= 1
integer INTEGER ::= 1
interleave INTEGER ::= 1
ischosen INTEGER ::= 1
ispresent INTEGER ::= 1
isvalue INTEGER ::= 1

kill INTEGER ::= 1
killed INTEGER ::= 1

label INTEGER ::= 1
language INTEGER ::= 1
length INTEGER ::= 1
lengthof INTEGER ::= 1
log INTEGER ::= 1
log2str INTEGER ::= 1

map INTEGER ::= 1
match INTEGER ::= 1
message INTEGER ::= 1
mixed INTEGER ::= 1
mod INTEGER ::= 1
modifies INTEGER ::= 1
module INTEGER ::= 1
modulepar INTEGER ::= 1
mtc INTEGER ::= 1

noblock INTEGER ::= 1
none INTEGER ::= 1
not INTEGER ::= 1
not4b INTEGER ::= 1
nowait INTEGER ::= 1
null INTEGER ::= 1

objid INTEGER ::= 1
oct2bit INTEGER ::= 1
oct2char INTEGER ::= 1
oct2hex INTEGER ::= 1
oct2int INTEGER ::= 1
oct2str INTEGER ::= 1
octetstring INTEGER ::= 1
of INTEGER ::= 1
omit INTEGER ::= 1
on INTEGER ::= 1
optional INTEGER ::= 1
or INTEGER ::= 1
or4b INTEGER ::= 1
out INTEGER ::= 1
override INTEGER ::= 1

param INTEGER ::= 1
pass INTEGER ::= 1
pattern INTEGER ::= 1
permutation INTEGER ::= 1
port INTEGER ::= 1
procedure INTEGER ::= 1

raise INTEGER ::= 1
read INTEGER ::= 1
receive INTEGER ::= 1
record INTEGER ::= 1
recursive INTEGER ::= 1
refers INTEGER ::= 1
regexp INTEGER ::= 1
rem INTEGER ::= 1
repeat INTEGER ::= 1
replace INTEGER ::= 1
reply INTEGER ::= 1
return INTEGER ::= 1
rnd INTEGER ::= 1
running INTEGER ::= 1
runs INTEGER ::= 1

select INTEGER ::= 1
self INTEGER ::= 1
send INTEGER ::= 1
sender INTEGER ::= 1
set INTEGER ::= 1
setverdict INTEGER ::= 1
signature INTEGER ::= 1
sizeof INTEGER ::= 1
start INTEGER ::= 1
stop INTEGER ::= 1
str2bit INTEGER ::= 1
str2float INTEGER ::= 1
str2hex INTEGER ::= 1
str2int INTEGER ::= 1
str2oct INTEGER ::= 1
subset INTEGER ::= 1
substr INTEGER ::= 1
superset INTEGER ::= 1
system INTEGER ::= 1

template INTEGER ::= 1
testcase INTEGER ::= 1
timeout INTEGER ::= 1
timer INTEGER ::= 1
to INTEGER ::= 1
trigger INTEGER ::= 1
true INTEGER ::= 1
type INTEGER ::= 1

unichar2char INTEGER ::= 1
unichar2int INTEGER ::= 1
union INTEGER ::= 1
universal INTEGER ::= 1
unmap INTEGER ::= 1

value INTEGER ::= 1
valueof INTEGER ::= 1
var INTEGER ::= 1
variant INTEGER ::= 1
verdicttype INTEGER ::= 1

while INTEGER ::= 1
with INTEGER ::= 1

xor INTEGER ::= 1
xor4b INTEGER ::= 1

END

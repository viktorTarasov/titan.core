--/////////////////////////////////////////////////////////////////////////////
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Szabados, Kristof
--
--/////////////////////////////////////////////////////////////////////////////
Test13
DEFINITIONS

AUTOMATIC TAGS

::=

BEGIN

MySequenceType1 ::= SET
		{
		field1 INTEGER OPTIONAL,
		field2 This-Is-An-Undefined-Type OPTIONAL
		}

END

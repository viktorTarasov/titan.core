--/////////////////////////////////////////////////////////////////////////////
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Szabados, Kristof
--
--/////////////////////////////////////////////////////////////////////////////
Test33
DEFINITIONS

IMPLICIT TAGS

::=

BEGIN

MySequenceType ::= SEQUENCE {
  			     field1  INTEGER,
			     field2 [0] BOOLEAN DEFAULT TRUE,
			     field3 [5] NULL OPTIONAL,
			     field4 [0] OCTET STRING DEFAULT 'FFFF'H,
			     field5 [2] BIT STRING ,
			     field6 [3] ENUMERATED {a,b,c} OPTIONAL,
			     field7 [4] REAL
			    }

END

--/////////////////////////////////////////////////////////////////////////////
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Baranyi, Botond
--
--/////////////////////////////////////////////////////////////////////////////
Test19-1
DEFINITIONS

AUTOMATIC TAGS

::=

BEGIN

minusone INTEGER ::= -1

MyBitstringType2 ::= BIT STRING{ first(0), second (minusone), last-in-first-octet(7) }

END

--/////////////////////////////////////////////////////////////////////////////
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Szabados, Kristof
--
--/////////////////////////////////////////////////////////////////////////////
Test26
DEFINITIONS

IMPLICIT TAGS

::=

BEGIN

MyChoiceType ::= CHOICE
			    {
  			     field1 [0] INTEGER,
			     field2 [1] BOOLEAN,
			     field3 [2] NULL,
			     field4 [3] OCTET STRING,
			     field5 [3] BIT STRING,
			     field6 [5] ENUMERATED {a,b,c},
			     field7 [6] REAL
			    }

END

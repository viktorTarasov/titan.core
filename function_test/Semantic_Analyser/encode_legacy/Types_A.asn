-------------------------------------------------------------------------------
-- Copyright (c) 2000-2018 Ericsson Telecom AB
-- All rights reserved. This program and the accompanying materials
-- are made available under the terms of the Eclipse Public License v2.0
-- which accompanies this distribution, and is available at
-- https://www.eclipse.org/org/documents/epl-2.0/EPL-2.0.html
--
-- Contributors:
--   Baranyi, Botond
--
-------------------------------------------------------------------------------

Types-A
DEFINITIONS

AUTOMATIC TAGS ::=

BEGIN
IMPORTS;

Int ::= INTEGER

Seq ::= SEQUENCE { --//Cannot determine the encoding rules for type `@Types-A.Seq'. Multiple encoding external functions found with different rules// //Cannot determine the decoding rules for type `@Types-A.Seq'. Multiple decoding external functions found with different rules//
  num INTEGER,
  str VisibleString
}

Set ::= SET {
  num INTEGER,
  str VisibleString
}

SeqOf ::= SEQUENCE OF INTEGER --//Cannot determine the encoding rules for type `@Types-A.SeqOf'. Multiple encoding external functions found with different rules// //Cannot determine the decoding rules for type `@Types-A.SeqOf'. Multiple decoding external functions found with different rules//

SetOf ::= SET OF INTEGER

Choice ::= CHOICE { --//Cannot determine the encoding rules for type `@Types-A.Choice'. Multiple encoding external functions found with different rules// //Cannot determine the decoding rules for type `@Types-A.Choice'. No decoding external functions found//
  num INTEGER,
  str VisibleString
}

END

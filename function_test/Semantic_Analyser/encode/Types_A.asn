-------------------------------------------------------------------------------
-- Copyright (c) 2000-2016 Ericsson Telecom AB
-- All rights reserved. This program and the accompanying materials
-- are made available under the terms of the Eclipse Public License v1.0
-- which accompanies this distribution, and is available at
-- http://www.eclipse.org/legal/epl-v10.html
--
-- Contributors:
--   Baranyi, Botond
--
-------------------------------------------------------------------------------

Types-A
DEFINITIONS

AUTOMATIC TAGS ::=

BEGIN
IMPORTS;

Int ::= INTEGER

Seq ::= SEQUENCE { --//Cannot determine the encoding rules for type `@Types-A.Seq'. Multiple encoding external functions found with different rules// //Cannot determine the decoding rules for type `@Types-A.Seq'. Multiple decoding external functions found with different rules//
  num INTEGER,
  str VisibleString
}

Set ::= SET {
  num INTEGER,
  str VisibleString
}

SeqOf ::= SEQUENCE OF INTEGER --//Cannot determine the encoding rules for type `@Types-A.SeqOf'. Multiple encoding external functions found with different rules// //Cannot determine the decoding rules for type `@Types-A.SeqOf'. Multiple decoding external functions found with different rules//

SetOf ::= SET OF INTEGER

Choice ::= CHOICE { --//Cannot determine the encoding rules for type `@Types-A.Choice'. Multiple encoding external functions found with different rules// //Cannot determine the decoding rules for type `@Types-A.Choice'. No decoding external functions found//
  num INTEGER,
  str VisibleString
}

END
